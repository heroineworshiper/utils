import libisogrid
import importlib
importlib.reload(libisogrid)



# side panel
if True:
    extrudeTris, extrudeSubs = libisogrid.makeGrid(33, \
        81, \
        2, \
        4, \
        [ 1.0, 1.0 ], \
        [ 1.0, 1.0 ], \
        0, \
        0, \
        2.4, \
        1)
    extrudeTris.Placement = App.Placement(
        App.Vector(8.6, -40.50, 37.00),
        App.Rotation(App.Vector(0, -1, 0), 270))

# front panel
if False:
    extrudeTris, extrudeSubs = libisogrid.makeGrid(33, \
        47, \
        2, \
        2, \
        [ 1.0, 1.0 ], \
        [ 1.0, 1.0 ], \
        0, \
        0, \
        2.4, \
        1)
    extrudeTris.Placement = App.Placement(
        App.Vector(-23.50, -25.60, 37.00),
        App.Rotation(App.Vector(.58, .58, -.58), 120))

# top
if False:
    extrudeTris, extrudeSubs = libisogrid.makeGrid(90.2, \
        56.2, \
        6, \
        3, \
        [ .5, .5 ], \
        [ .5, .5 ], \
        0, \
        0, \
        2.4, \
        1)
    extrudeTris.Placement = App.Placement(
        App.Vector(-28.10, 45.10, 17.00),
        App.Rotation(App.Vector(0, 0, 1), 270.00))


# bottom
if False:
    extrudeTris, extrudeSubs = libisogrid.makeGrid(96, \
        62, \
        6, \
        3, \
        [ 1, 1 ], \
        [ 1, 1 ], \
        0, \
        0, \
        2.6, \
        1)
    extrudeTris.Placement = App.Placement(
        App.Vector(-31, 48, -19),
        App.Rotation(App.Vector(0, 0, 1), 270.00))
